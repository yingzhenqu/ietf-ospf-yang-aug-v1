module ietf-ospf-link-attr {
  yang-version 1.1;
  namespace "urn:ietf:params:xml:ns:yang:ietf-ospf-link-attr";
  prefix ospf-link-attr;

  import ietf-routing {
    prefix rt;
    reference
      "RFC 8349: A YANG Data Model for Routing
                 Management (NMDA Version)";
  }
  import ietf-te-types {
    prefix te-types;
    reference
      "RFC 8776: Common YANG Data Types for Traffic Engineering.";
  }
  import ietf-ospf {
    prefix ospf;
    reference
      "RFC 9129: YANG Data Model for the OSPF Protocol";
  }
  import ietf-ospfv3-extended-lsa {
    prefix ospfv3-e-lsa;
    reference
      "RFC 9587: YANG Data Model for OSPFv3 Extended Link
                 State Advertisements (LSAs)";
  }
  import iana-igp-link-attr-apps {
    prefix iana-link-attr-apps;
    reference
      "RFC XXXX: YANG Data Model for OSPF Application-Specific
                 Link Attributes and Flexible Algorithm";
  }

  organization
    "IETF LSR - Link State Routing Working Group";
  contact
    "WG Web:   <https://datatracker.ietf.org/wg/lsr/>
     WG List:  <mailto:lsr@ietf.org>

     Author:   Yingzhen Qu
               <mailto:yingzhen.ietf@gmail.com>
     Author:   Acee Lindem
               <mailto:acee.ietf@gmail.com>
    ";
  description
    "This YANG module defines the configuration and operational
     state for OSPF application specific link attributes feature
     as defined in RFC 9492.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX;
     see the RFC itself for full legal notices.

      The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-07-09 {
    description
      "Initial version";
    reference
      "RFC XXXX: A YANG Data Model for OSPF Application-Specific
                 Link Attributes and Flexible Algorithm";
  }

  typedef attr-advertise-mode {
    type enumeration {
      enum legacy {
        value 0;
        description
          "Only send legacy advertisements, and no ASLA
           advertisement. Legacy advertisements will be
           used for the application.";
        reference
          "RFC9492: OSPF Application-Specific Attributes,
           Section 12.3.3";
      }
      enum transition {
        value 1;
        description
          "Send both application-specific and legacy
           advertisements. Both application-specific and
           legacy attribute advertisements will be used
           by the application with advertised legacy attributes
           taking precedence.";
        reference
          "RFC9492: OSPF Application-Specific Attributes,
           Section 12.3.3";
      }
      enum app-specific {
        value 2;
        description
          "Application-specific advertisements are advertised
           exclusively except for RSVP-TE in certain situations.
           Refer to the reference for the specific rules.";
        reference
          "RFC9492: OSPF Application-Specific Attributes,
           Section 12.3.3 and Section 12.3.4.";
      }
    }
    description
      "Link attributes operation mode.";
    reference
      "RFC 9492 - OSPF Application-Specific Link Attributes,
       Section 12.3.";
  }

  grouping ospf-te-link-attrs {
    description
      "OSPF Application-Specific Link Attributes (ASLA)
       inherited from the base OSPF TE attributes";
    leaf te-metric {
      type te-types:te-metric;
      description
        "TE metric.";
      reference
        "RFC 3630 - Traffic Engineering (TE) Extensions
         to OSPFv2";
    }
    leaf admin-group {
      type te-types:admin-group;
      description
        "Administrative Group / Resource Class/Color.";
      reference
        "RFC 3630 - Traffic Engineering (TE) Extensions
         to OSPFv2";
    }
    reference
      "RFC 3630 - Traffic Engineering (TE) Extensions
       to OSPFv2";
  }

  grouping app-specific-link-attr-sub-tlvs {
    description
      "OSPF Application-Specific Link Attributes (ASLA) sub-TLV.
       The ASLA sub-TLV is a sub-TLV of the OSPFv2 Extended Link
       TLV (RFC7684) and OSPFv3 Router-Link TLV (RFC8362).";
    container app-specific-link-attr-sub-tlvs {
      description
        "Application-Specific Link Attributes sub-TLV.";
      list asla-sub-tlv {
        container sabm {
          leaf-list sabm-bit {
            type iana-link-attr-apps:igp-link-attr-app;
            description
              "Standard Application Identifier Bit Mask bits. This
               leaf-list contains enums for the bits which are
               set to 1 in the SABM field.";
          }
          description
            "Standard Application Identifier Bit Mask.";
          reference
            "RFC 9492: OSPF Application-Specific Link Attributes,
             Section 5";
        }
        container udabm {
          description
            "User Defined Application Identifier Bit Mask (UDABM).
             This container is intended to be augmented by documents
             defining user-defined application identifiers.  Each
             such augmentation SHOULD add a leaf-list of identityref
             type whose base identity represents the user-defined
             application, following the same pattern as the
             'sabm-bit' leaf-list.  Refer to RFC 9492, Section 5
             for the on-wire encoding of the UDABM field.";
          reference
            "RFC 9492: OSPF Application-Specific Link Attributes,
             Section 5";
        }
        container link-attributes-sub-tlvs {
          uses ospf-te-link-attrs;
          uses ospf:unknown-tlvs;
          description
            "Link Attributes sub-TLVs.";
        }
        description
          "List of application-Specific Link Attributes sub-TLVs.";
      }
    }
    reference
      "RFC 9492: OSPF Application-Specific Link Attributes";
  }

  /* Configuration */

  augment "/rt:routing/rt:control-plane-protocols"
        + "/rt:control-plane-protocol/ospf:ospf" {
    when "derived-from-or-self(../rt:type, 'ospf:ospfv2') or "
       + "derived-from-or-self(../rt:type, 'ospf:ospfv3')" {
      description
        "This augments the OSPF routing protocol when used.";
    }
    description
      "This augments OSPF protocol configuration
       with application-specific link attributes.";
    reference
      "RFC 9492: OSPF Application-Specific Link Attributes,
       Section 12.3";
    container ospf-link-attr {
      description
        "Configuration of application attribute advertisement
         and usage.";
      leaf rsvp-te-advertise {
        type attr-advertise-mode;
        default "legacy";
        description
          "Advertisement for RSVP-TE - The default will be
           'legacy' and RSVP-TE advertisement (e.g., OSPFv2 Opaque
           TE LSAs and OSPFv3 TE LSA will be advertised
           independent of configuration if certain attributes are
           advertised).";
        reference
          "RFC 9492: OSPF Application-Specific Link Attributes,
           Section 12.3.4.";
      }
      leaf lfa-advertise {
        type attr-advertise-mode;
        default "app-specific";
        description
          "Advertisement for Link Free Alternates (LFA) - The
           default will be 'app-specific'. ASLA advertisements will
           be advertised and used by default unless specified
           otherwise.";
        reference
          "RFC 9492: OSPF Application-Specific Link Attributes,
           Section 12.3.";
      }
      leaf sr-policy-advertise {
        type attr-advertise-mode;
        default "app-specific";
        description
          "Advertisement for Segment Routing Policy (SR-Policy) -
           The default will be 'app-specific'. ASLA advertisements
           will be advertised and used by default unless specified
           otherwise.";
        reference
          "RFC 9492: OSPF Application-Specific Link Attributes,
           Section 12.3.";
      }
    }
  }

  augment "/rt:routing/rt:control-plane-protocols/"
        + "rt:control-plane-protocol/ospf:ospf/"
        + "ospf:areas/ospf:area/ospf:interfaces/ospf:interface" {
    when "derived-from-or-self(../../../../../rt:type, "
       + "'ospf:ospfv2') or "
       + "derived-from-or-self(../../../../../rt:type, "
       + "'ospf:ospfv3')" {
      description
        "This augments the OSPF interface configuration.";
    }
    description
      "This augments OSPF interface configuration
       with Application Specific Link Attributes (ASLA).";
    container ospf-asla {
      list interface-asla {
        key "link-attr-app";
        leaf link-attr-app {
          type iana-link-attr-apps:igp-link-attr-app;
          description
            "Application-specific attributes. Note that
             when encoded, applications with identical
             attributes may be included in the same sub-TLV.";
        }
        uses ospf-te-link-attrs;
        description
          "ASLA interface configuration.";
      }
      description
        "Application specific link attributes configuration.";
    }
  }

  /* Database */

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-link-opaque/ospf:extended-link-tlv" {
    when "derived-from-or-self("
       + "../../../../../../../../../../../../rt:type, "
       + "'ospf:ospfv2')" {
      description
        "This augmentation is only valid for OSPFv2.";
    }
    description
      "OSPF Application-Specific Link Attributes (ASLA) sub-TLV is
       a sub-TLV of OSPFv2 Extended Link TLV (RFC7684).";
    uses app-specific-link-attr-sub-tlvs;
  }

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-router/"
        + "ospfv3-e-lsa:e-router-tlvs/ospfv3-e-lsa:link-tlv" {
    when "derived-from-or-self("
       + "../../../../../../../../../../../../rt:type, "
       + "'ospf:ospfv3')" {
      description
        "This augmentation is only valid for OSPFv3
         E-Router LSAs";
    }
    description
      "Augment OSPFv3 Area scope router-link TLV.";
    uses app-specific-link-attr-sub-tlvs;
  }
}
