module iana-igp-algo-types {
  yang-version 1.1;
  namespace "urn:ietf:params:xml:ns:yang:iana-igp-algo-types";
  prefix iana-algo-types;

  organization
    "Internet Assigned Numbers Authority (IANA)";
  contact
    "Internet Assigned Numbers Authority

     ICANN
     12025 Waterfront Drive, Suite 300
     Los Angeles, CA 90094-2536
     United States of America

     Tel:    +1 310 301 5800
      &lt;mailto:iana@iana.org&gt;";
  description
    "The YANG module defines the YANG data types for IANA-registered
     Interior Gateway Protocol (IGP) Algorithm Types.

     This YANG module is maintained by IANA and reflects the 'IGP
     Algorithm Types' registry.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This initial version of this YANG module is part of RFC XXXX
     (https://www.rfc-editor.org/info/rfcXXXX); see the RFC itself
     for full legal notices.

     //RFC Ed.: replace XXXX with actual RFC number and remove
       this note

     The latest version of this YANG module is available at
     https://www.iana.org/assignments/yang-parameters.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  reference
    "Interior Gateway Protocol (IGP) Parameters, IGP Algorithm Types
     (https://www.iana.org/assignments/igp-parameters/
      igp-parameters.xhtml#igp-algorithm-types)";

  revision 2026-07-02 {
    description
      "Initial Version";
    reference
      "RFC XXXX: YANG Data Model for OSPF Application-Specific
                 Link Attributes and Flexible Algorithm";
  }

  typedef algo-type {
    type enumeration {
      enum algo-spf {
        value 0;
        description
          "Shortest Path First (SPF) algorithm based on link metric.
          This is the standard shortest path algorithm as computed by
          the IGP protocol. Consistent with the deployed practice for
          link-state protocols, Algorithm 0 permits any node to 
          overwrite the SPF path with a different path based on its
          local policy.";
        reference
          "RFC 8665: OSPF Extensions for Segment Routing";
      }    

      enum algo-strict-spf {
        value 1;
        description
          "Strict Shortest Path First (SPF) algorithm based on
          link metric. The algorithm is identical to Algorithm 0 but
          Algorithm 1 requires that all nodes along the path will
          honor the SPF routing decision. Local policy at the node
          claiming support for Algorithm 1 MUST NOT alter the SPF
          paths computed by Algorithm 1.";
        reference
          "RFC 8665: OSPF Extensions for Segment Routing";
      }

    }
    default "algo-spf";
    description
      "IGP Algorithm Type. The algorithm types are defined in IANA
       IGP Algorithm Types registry";
  }
}
