module iana-igp-link-attr-apps {
  yang-version 1.1;
  namespace "urn:ietf:params:xml:ns:yang:iana-igp-link-attr-apps";
  prefix iana-link-attr-apps;

  organization
    "Internet Assigned Numbers Authority (IANA)";
  contact
    "Internet Assigned Numbers Authority

     ICANN
     12025 Waterfront Drive, Suite 300
     Los Angeles, CA 90094-2536
     United States of America

     Tel:    +1 310 301 5800
      &lt;mailto:iana@iana.org&gt;";
  description
    "The YANG module defines the YANG data types for IANA-registered
     Interior Gateway Protocol (IGP) Application IDs used for Link
     Attributes.

     This YANG module is maintained by IANA and reflects the 'Link
     Attribute Application Identifiers' registry.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This initial version of this YANG module is part of RFC XXXX
     (https://www.rfc-editor.org/info/rfcXXXX); see the RFC itself
     for full legal notices.

     //RFC Ed.: replace XXXX with actual RFC number and remove
       this note

     The latest version of this YANG module is available at
     https://www.iana.org/assignments/yang-parameters.";

  reference
    "Interior Gateway Protocol (IGP) Parameters, IGP Algorithm Types
     (https://www.iana.org/assignments/igp-parameters/
      igp-parameters.xhtml#link-attribute-application-identifiers)";

  revision 2026-07-02 {
    description
      "Initial Version";
    reference
      "RFC XXXX: YANG Data Model for OSPF Application-Specific
                 Link Attributes and Flexible Algorithm";
  }

  typedef igp-link-attr-app {
    type enumeration {
      enum rsvp-te-app {
        value 0;
        description
          "RSVP-TE (R-bit).";
        reference
          "RFC 9479: IS-IS Application-Specific Link Attributes";
      }    

      enum segment-routing-policy-app {
        value 1;
        description
          "Segment Routing Policy (S-bit).";
        reference
          "RFC 9479: IS-IS Application-Specific Link Attributes";
      }    

      enum loop-free-alternate-app {
        value 2;
        description
          "Loop-Free Alternate (F-bit).";
        reference
          "RFC 9479: IS-IS Application-Specific Link Attributes";
      }    

      enum flexible-algorithm-app {
        value 3;
        description
          "Flexible Algorithm (X-bit).";
        reference
          "RFC 9350: IGP Flexible Algorithm, Section 12.";
      }
    }
    description
      "Application IDs used for Link Attributes, which are defined
      in the IANA Link Attribute Application Identifiers registry.";
    reference
      "RFC 9479: IS-IS Application-Specific Link Attributes";
  }
}
