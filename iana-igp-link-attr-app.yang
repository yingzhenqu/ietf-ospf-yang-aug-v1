module iana-igp-link-attr-app {
  yang-version 1.1;
  namespace "urn:ietf:params:xml:ns:yang:iana-igp-link-attr-app";
  prefix iana-link-attr-app;

  organization
    "Internet Assigned Numbers Authority (IANA)";
  contact
    "Internet Assigned Numbers Authority

     ICANN
     12025 Waterfront Drive, Suite 300
     Los Angeles, CA 90094-2536
     United States of America

     Tel:    +1 310 301 5800
      &lt;mailto:iana@iana.org&gt;";
  description
    "The YANG module defines the identities for Interior Gateway
     Protocol (IGP) Application IDs used for Link Attributes.

     This YANG module is maintained by IANA and reflects the 'Link
     Attribute Application Identifiers' registry.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This initial version of this YANG module is part of RFC XXXX
     (https://www.rfc-editor.org/info/rfcXXXX); see the RFC itself
     for full legal notices.

     //RFC Ed.: replace XXXX with actual RFC number and remove
       this note

     The latest version of this YANG module is available at
     https://www.iana.org/assignments/yang-parameters.";

  revision 2026-04-08 {
    description
      "Initial Version";
    reference
      "RFC XXXX: YANG Data Model for OSPF Application-Specific
                 Link Attributes and Flexible Algorithm";
  }

  identity igp-link-attr-app {
    description
      "Base identity for Standard Applications";
    reference
      "RFC 9492: OSPF Application-Specific Link Attributes";
  }

  identity rsvp-te-app {
    base igp-link-attr-app;
    description
      "RSVP Traffic Engineering (TE) Application - This
       corresponds to Bit 0 (R-BIT) in the Standard Application
       Bit Mask (SABM).";
    reference
      "RFC 3630: Traffic Engineering (TE) for OSPFv2
       RFC 5329: Traffic Engineering Extensions to OSPFv3";
  }

  identity sr-policy-app {
    base igp-link-attr-app;
    description
      "Segment Routing (SR) Policy Application - This
       corresponds to Bit 1 (S-BIT) in the Standard Application
       Bit Mask (SABM).";
    reference
      "RFC 8665: OSPF Extensions for Segment Routing
       RFC 8666: OSPFv3 Extensions for Segment Routing";
  }

  identity lfa-app {
    base igp-link-attr-app;
    description
      "Loop-Free Alternative (LFA) Application - This
       corresponds to Bit 2 (F-BIT) in the Standard Application
       Bit Mask (SABM).";
    reference
      "RFC 8102: Remote-LFA Node Protection and Manageability
       RFC 9855: Topology Independent Fast Reroute Using
                 Segment Routing";
  }

  identity flex-algo-app {
    base igp-link-attr-app;
    description
      "Flexible Algorithm Application - This
       corresponds to Bit 3 (X-BIT) in the Standard Application
       Bit Mask (SABM).";
    reference
      "RFC 9350: IGP Flexible Algorithm, Section 12.";
  }
}
