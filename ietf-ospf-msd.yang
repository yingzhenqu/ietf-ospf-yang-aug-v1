module ietf-ospf-msd {
  yang-version 1.1;
  namespace "urn:ietf:params:xml:ns:yang:ietf-ospf-msd";
  prefix ospf-msd;

  import ietf-routing {
    prefix rt;
    reference "RFC 8349: A YANG Data Model for Routing
               Management (NMDA Version)";
  }

  import ietf-ospf {
    prefix ospf;
    reference "RFC 9129: YANG Data Model for the OSPF
               Protocol";
  }

  import ietf-ospfv3-extended-lsa {
    prefix ospfv3-e-lsa;
    reference "RFC 9587: YANG Data Model for OSPFv3 Extended Link
               State Advertisements (LSAs)";
  }

  import iana-msd-types {
    prefix iana-msd-types;
  }

  organization
    "IETF LSR - LSR Working Group";
  contact
    "WG Web:   <https://datatracker.ietf.org/wg/lsr/>
     WG List:  <mailto:lsr@ietf.org>

     Author:    Yingzhen Qu
               <mailto:yingzhen.ietf@gmail.com>
     Author:    Acee Lindem
               <mailto:acee.ietf@gmail.com>
     Author:    Stephane Litkowski
               <mailto:slitkows.ietf@gmail.com>
     Author:    Jeff Tantsura
               <jefftant.ietf@gmail.com>

    ";
  description
    "The YANG module augments the base OSPF model to
     manage different types of MSDs.

     This YANG model conforms to the Network Management
     Datastore Architecture (NMDA) as described in RFC 8342.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";


  reference "RFC XXXX: YANG Data Model for OSPF MSD.";

  revision 2025-03-01 {
    description
      "Initial Version";
    reference
      "RFC XXXX: OSPF YANG Model Augmentations for Additional
                 Features - Version 1.";
  }

  grouping node-msd-tlv {
    description
      "Grouping for node MSD.";
    container node-msd-tlv {
      list node-msds {
        key "msd-type";
        leaf msd-type {
          type identityref {
          base iana-msd-types:msd-base-mpls;
          }
          description
            "MSD-Types";
        }
        leaf msd-value {
          type uint8;
          description
            "MSD value, in the range of 0-255.";
        }
        description
          "Node MSD is the smallest link MSD supported by
           the node.";
      }
      description
        "Node MSD is the number of SIDs supported by a node.";
      reference
        "RFC 8476: Signaling Maximum SID Depth (MSD) Using OSPF";
    }
  }

  grouping link-msd-sub-tlv {
    description
      "Link Maximum SID Depth (MSD) grouping for an interface.";
    container link-msd-sub-tlv {
      list link-msds {
        key "msd-type";
        leaf msd-type {
          type identityref {
            base iana-msd-types:msd-base-mpls;
          }
          description
            "MSD-Types";
        }
        leaf msd-value {
          type uint8;
          description
            "MSD value, in the range of 0-255.";
        }
        description
          "List of link MSDs";
      }
      description
        "Link MSD sub-tlvs.";
    }
  }

  /* Node MSD TLV */
  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:ri-opaque" {
    when "../../../../../../../../../../../"
       + "rt:type = 'ospf:ospfv2'" {
      description
        "This augmentation is only valid for OSPFv2.";
    }
    description
      "Node MSD TLV is an optional TLV of OSPFv2 RI Opaque
       LSA (RFC7770) and has a type of 12.";

    uses node-msd-tlv;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque/"
        + "ospf:ri-opaque" {
    when "../../../../../../../../../"
       + "rt:type = 'ospf:ospfv2'" {
      description
        "This augmentation is only valid for OSPFv2.";
    }
    description
      "Node MSD TLV is an optional TLV of OSPFv2 RI Opaque
       LSA (RFC7770) and has a type of 12.";

    uses node-msd-tlv;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv3/"
        + "ospf:ospfv3/ospf:body/ospf:router-information" {
    when "../../../../../../../../../../"
       + "rt:type = 'ospf:ospfv3'" {
      description
        "This augmentation is only valid for OSPFv3.";
    }
    description
      "Node MSD TLV is an optional TLV of OSPFv3 RI Opaque
       LSA (RFC7770) and has a type of 12.";

    uses node-msd-tlv;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body/ospf:router-information" {
    when "../../../../../../../../"
       + "rt:type = 'ospf:ospfv3'" {
      description
        "This augmentation is only valid for OSPFv3.";
    }
    description
      "Node MSD TLV is an optional TLV of OSPFv3 RI Opaque
       LSA (RFC7770) and has a type of 12.";

    uses node-msd-tlv;
  }

  /* link MSD sub-tlv */
  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-link-opaque/ospf:extended-link-tlv" {
    when "../../../../../../../../../../../../"
       + "rt:type = 'ospf:ospfv2'" {
      description
        "This augmentation is only valid for OSPFv2.";
    }
    description
      "Link MSD sub-TLV is an optional sub-TLV of OSPFv2 extended
       link TLV as defined in RFC 7684 and has a type of 6.";

    uses link-msd-sub-tlv;
  }

  augment "/rt:routing/"
       + "rt:control-plane-protocols/rt:control-plane-protocol/"
       + "ospf:ospf/ospf:areas/ospf:area/ospf:database/"
       + "ospf:area-scope-lsa-type/ospf:area-scope-lsas/"
       + "ospf:area-scope-lsa/ospf:version/ospf:ospfv3/"
       + "ospf:ospfv3/ospf:body/ospfv3-e-lsa:e-router/"
       + "ospfv3-e-lsa:e-router-tlvs/ospfv3-e-lsa:link-tlv" {
       when "'ospf:../../../../../../../../"
         + "rt:type' = 'ospf:ospfv3'" {
         description
           "This augmentation is only valid for OSPFv3
            E-Router LSAs";
       }
    description
      "Augment OSPFv3 Area scope router-link TLV.";

    uses link-msd-sub-tlv;
  }
}
