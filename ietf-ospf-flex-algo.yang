module ietf-ospf-flex-algo {
  yang-version 1.1;
  namespace "urn:ietf:params:xml:ns:yang:ietf-ospf-flex-algo";
  prefix ospf-flex-algo;

  import ietf-routing {
    prefix rt;
    reference
      "RFC 8349: A YANG Data Model for Routing
       Management (NMDA Version)";
  }
  import ietf-routing-types {
    prefix rt-types;
    reference
      "RFC 8294: Common YANG Data Types for the
       Routing Area";
  }
  import ietf-te-types {
    prefix te-types;
    reference
      "RFC 8776: Common YANG Data Types for Traffic Engineering.";
  }
  import ietf-ospf {
    prefix ospf;
    reference
      "RFC 9129: YANG Data Model for the OSPF
       Protocol";
  }
  import ietf-ospfv3-extended-lsa {
    prefix ospfv3-e-lsa;
    reference
      "RFC 9587: YANG Data Model for OSPFv3 Extended Link
       State Advertisements (LSAs)";
  }
  import iana-igp-algo-types {
    prefix iana-algo-types;
    reference
      "IANA IGP Algorithm Types registry,
       <https://www.iana.org/assignments/igp-parameters>.";
  }
  import iana-igp-metric-types {
    prefix iana-metric-types;
    reference
      "IANA IGP Metric-Type registry,
       <https://www.iana.org/assignments/igp-parameters>.";
  }

  organization
    "IETF LSR - Link State Routing Working Group";
  contact
    "WG Web:   <https://datatracker.ietf.org/wg/lsr/>
     WG List:  <mailto:lsr@ietf.org>

     Author:    Yingzhen Qu
                <mailto:yingzhen.ietf@gmail.com>
     Author:    Acee Lindem
                <mailto:acee.ietf@gmail.com>
    ";
  description
    "The YANG module defines the configuration and operational
     state for OSPF Flexible Algorithm as defined in RFC 9350.

     Copyright (c) 2026 IETF Trust and the persons identified as
     authors of the code.  All rights reserved.

     Redistribution and use in source and binary forms, with or
     without modification, is permitted pursuant to, and subject
     to the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-07-09 {
    description
      "Initial Version";
    reference
      "RFC XXXX: A YANG Data Model for OSPF Application-Specific
                 Link Attributes and Flexible Algorithm";
  }

  /* Identities */

  identity fad-flags {
    description
      "Base identity for OSPF FAD flags.";
    reference
      "RFC 9350: IGP Flexible Algorithm, Section 7";
  }

  identity m-flag {
    base fad-flags;
    description
      "M-flag in the Flex-Algorithm Definition (FAD) flags sub-TLV.
       When this flag is present in the fad-flags leaf-list, the
       Flex-Algorithm-specific prefix metric is used for inter-area
       and external prefix calculation.  Note that this flag is not
       applicable to prefixes advertised as SRv6 locators.";
    reference
      "RFC 9350: IGP Flexible Algorithm, Section 7.4";
  }

  identity fapm-flags {
    description
      "Base identity for OSPF flex-algo prefix metric flags.";
    reference
      "RFC 9350: IGP Flexible Algorithm";
  }

  identity e-bit {
    base fapm-flags;
    description
      "External metric, if set, the metric specified is a
       type 2 external metric.";
    reference
      "RFC 9350: IGP Flexible Algorithm";
  }

  /* Groupings */

  grouping fad-tlvs {
    container fad-tlvs {
      list fad-tlv {
        leaf algo-number {
          type uint8;
          description
            "Flex-algo number - A value not in the inclusive range
             of 128-255 is an invalid FAD TLV specification. There
             should only be a single FAD TLV per algorithm number.";
        }
        leaf metric-type {
          type iana-metric-types:metric-type;
          description
            "Type of metric to be used during the calculation.";
        }
        leaf calc-type {
          type iana-algo-types:algo-type;
          description
            "IGP algorithm types, value from 0 to 127 as
             defined under 'Interior Gateway Protocol (IGP)
             Parameter' by IANA.";
        }
        leaf priority {
          type uint8;
          description
            "Priority of the advertisement.";
        }
        container fa-ex-ag-sub-tlv {
          leaf extended-admin-group {
            type te-types:extended-admin-group;
            description
              "Extended administrative group as defined in
               RFC 7308.";
          }
          description
            "The flex-algo exclude admin group sub-tlv.";
        }
        container fa-in-any-ag-sub-tlv {
          leaf extended-admin-group {
            type te-types:extended-admin-group;
            description
              "Extended administrative group as defined in
               RFC 7308.";
          }
          description
            "The flex-algo include-any admin group sub-tlv.";
        }
        container fa-in-all-ag-sub-tlv {
          leaf extended-admin-group {
            type te-types:extended-admin-group;
            description
              "Extended administrative group as defined in
               RFC 7308.";
          }
          description
            "The flex-algo include-all admin group sub-tlv.";
        }
        container fad-flags-sub-tlv {
          leaf-list fad-flag {
            type identityref {
              base fad-flags;
            }
            description
              "Flex-algo definition flags list.";
          }
          description
            "OSPF flex-algo definition flags.";
        }
        container fa-ex-srlg-sub-tlv {
          leaf-list srlg {
            type te-types:srlg;
            description
              "SRLG value as defined in RFC 4203.";
          }
          description
            "The flex-algo exclude SRLG sub-tlv.";
        }
        uses ospf:unknown-tlvs;
        description
          "List of flex-algo definition TLVs.";
      }
      description
        "OSPF Flexible Algorithm Definition TLV.";
    }
    description
      "OSPF Flexible Algorithm Definition (FAD) TLV.";
    reference
      "RFC 9350: IGP Flexible Algorithm";
  }

  grouping fapm-sub-tlvs {
    container fapm-sub-tlvs {
      list fapm-sub-tlv {
        leaf algo-number {
          type uint8;
          description
            "Flex-algo number - A value not in the inclusive range
             of 128-255 is an invalid FAD TLV specification.";
        }
        leaf-list fapm-flag {
          type identityref {
            base fapm-flags;
          }
          description
            "Flex-algo prefix metric flags list.";
        }
        leaf metric {
          type uint32;
          description
            "Prefix metric.";
        }
        description
          "List of flex-algo prefix sub-tlvs.";
      }
      description
        "Flex-algo prefix metric sub-tlvs.";
    }
    description
      "Flexible Algorithm Prefix Metric (FAPM) sub-TLVs.";
    reference
      "RFC 9350: IGP Flexible Algorithm";
  }

  grouping faam-sub-tlvs {
    container faam-sub-tlvs {
      list faam-sub-tlv {
        leaf algo-number {
          type uint8;
          description
            "Flex-algo number - A value not in the inclusive range
             of 128-255 is an invalid FAAM Sub-TLV specification.";
        }
        leaf metric {
          type uint32;
          description
            "Prefix metric.";
        }
        description
          "List of faam sub-tlvs.";
      }
      description
        "Flexible Algorithm ASBR Metric (FAAM) Sub-TLVs.";
    }
    description
      "Flexible Algorithm ASBR Metric (FAAM) Sub-TLVs.";
    reference
      "RFC 9350: IGP Flexible Algorithm";
  }

  /* Management */

  augment "/rt:routing/rt:control-plane-protocols"
        + "/rt:control-plane-protocol/ospf:ospf" {
    when "derived-from-or-self(../rt:type, 'ospf:ospfv2') or "
       + "derived-from-or-self(../rt:type, 'ospf:ospfv3')" {
      description
        "This augments the OSPF routing protocol when used.";
    }
    description
      "This augments OSPF protocol with Flexible
       Algorithm.";
    container ospf-flex-algo {
      list flex-algo {
        key "algo-number";
        leaf algo-number {
          type uint8 {
            range "128..255";
          }
          description
            "An identifier associated with the Flexible Algorithm
             Definition.";
        }
        leaf advertise-definition {
          type boolean;
          default "true";
          description
            "Enable to advertise the flex-algo definition.";
        }
        container admin-groups {
          if-feature "te-types:named-extended-admin-groups";
          leaf exclude-admin-group {
            type te-types:extended-admin-group;
            description
              "Exclude rule used during the flex-algo
               path computation.";
          }
          leaf include-any-admin-group {
            type te-types:extended-admin-group;
            description
              "The flex-algo include-any admin group. Note that the
               presence of more than one Include-Any Extended Admin
              Group will result in an invalid FAD TLV.";
          }
          leaf include-all-admin-group {
            type te-types:extended-admin-group;
            description
              "The flex-algo include-all admin group. Note that the
               presence of more than one Include-All Extended Admin
               Group will result in an invalid FAD TLV.";
          }
          description
            "Specify links for the flex-algo path computation.";
        }
        leaf-list exclude-srlg {
          type te-types:srlg;
          description
            "Shared Risk Link Groups (SRLGs) to be excluded during
             the flex-algo path computation.";
        }
        leaf calc-type {
          type iana-algo-types:algo-type;
          description
            "Calculation-type. Value from 0-127 inclusive from the
             IANA 'IGP Algorithm Types' registry defined under the
             'Interior Gateway Protocol (IGP) Parameters' registry.";
        }
        leaf metric-type {
          type iana-metric-types:metric-type;
          description
            "Type of metric to be used during the calculation.";
        }
        container prefix-metric {
          presence "Use flex-algo specific prefix metric.";
          description
            "Use flex-algo prefix metric.";
        }
        leaf priority {
          type uint8;
          description
            "Priority of the advertisement.";
        }
        description
          "List of flex-algo configurations.";
      }
      description
        "Flexible Algorithm configuration.";
    }
  }

  /* Database */

  augment "/rt:routing/"
        + "rt:control-plane-protocols/rt:control-plane-protocol/"
        + "ospf:ospf/ospf:areas/ospf:area/"
        + "ospf:interfaces/ospf:interface/ospf:database/"
        + "ospf:link-scope-lsa-type/ospf:link-scope-lsas/"
        + "ospf:link-scope-lsa/ospf:version/ospf:ospfv2/"
        + "ospf:ospfv2/ospf:body/ospf:opaque/ospf:ri-opaque" {
    when "derived-from-or-self(../../../../../../../../../../../.."
       + "/../rt:type, 'ospf:ospfv2')" {
      description
        "This augmentation is only valid for OSPFv2.";
    }
    description
      "Flex-algo definition TLVs for OSPFv2 type 9 opaque RI LSA.";
    uses fad-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/ospf:ri-opaque" {
    when "derived-from-or-self(../../../../../../../../../../.."
       + "/rt:type, 'ospf:ospfv2')" {
      description
        "This augmentation is only valid for OSPFv2.";
    }
    description
      "Flex-algo definition TLVs for OSPFv2 type 10 opaque RI LSA.";
    uses fad-tlvs;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque/ospf:ri-opaque" {
    when "derived-from-or-self(../../../../../../../../../rt:type,"
       + " 'ospf:ospfv2')" {
      description
        "This augmentation is only valid for OSPFv2.";
    }
    description
      "Flex-algo definition TLVs for OSPFv2 type 11 opaque RI LSA.";
    uses fad-tlvs;
  }

  augment "/rt:routing/"
        + "rt:control-plane-protocols/rt:control-plane-protocol/"
        + "ospf:ospf/ospf:areas/ospf:area/"
        + "ospf:interfaces/ospf:interface/ospf:database/"
        + "ospf:link-scope-lsa-type/ospf:link-scope-lsas/"
        + "ospf:link-scope-lsa/ospf:version/ospf:ospfv3/"
        + "ospf:ospfv3/ospf:body/ospf:router-information" {
    when "derived-from-or-self(../../../../../../../../../../../.."
       + "/rt:type, 'ospf:ospfv3')" {
      description
        "This augmentation is only valid for OSPFv3.";
    }
    description
      "Flex-algo definition TLVs for OSPFv3 Router
       Information (RI) LSA.";
    uses fad-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv3/"
        + "ospf:ospfv3/ospf:body/ospf:router-information" {
    when "derived-from-or-self(../../../../../../../../../../"
       + "rt:type, 'ospf:ospfv3')" {
      description
        "This augmentation is only valid for OSPFv3.";
    }
    description
      "Flex-algo definition TLVs for OSPFv3 Router
       Information (RI) LSA.";
    uses fad-tlvs;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body/ospf:router-information" {
    when "derived-from-or-self(../../../../../../../../rt:type, "
       + "'ospf:ospfv3')" {
      description
        "This augmentation is only valid for OSPFv3.";
    }
    description
      "Flex-algo definition TLVs for OSPFv3 Router Information LSA.";
    uses fad-tlvs;
  }

  augment "/rt:routing/"
        + "rt:control-plane-protocols/rt:control-plane-protocol/"
        + "ospf:ospf/ospf:areas/ospf:area/"
        + "ospf:interfaces/ospf:interface/ospf:database/"
        + "ospf:link-scope-lsa-type/ospf:link-scope-lsas/"
        + "ospf:link-scope-lsa/ospf:version/ospf:ospfv2/"
        + "ospf:ospfv2/ospf:body/ospf:opaque/"
        + "ospf:extended-prefix-opaque/ospf:extended-prefix-tlv" {
    when "derived-from-or-self(../../../../../../../../../../../.."
       + "/../../rt:type, 'ospf:ospfv2')" {
      description
        "This augmentation is only valid for OSPFv2.";
    }
    description
      "Flex-algo prefix metric sub-TLVs for OSPFv2 extended
       prefix TLV in type 9 opaque LSA.";
    uses fapm-sub-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-prefix-opaque/ospf:extended-prefix-tlv" {
    when "derived-from-or-self(../../../../../../../../../../../.."
       + "/rt:type, 'ospf:ospfv2')" {
      description
        "This augmentation is only valid for OSPFv2.";
    }
    description
      "Flex-algo prefix metric sub-TLVs for OSPFv2 extended
       prefix TLV in type 10 opaque LSA.";
    uses fapm-sub-tlvs;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque/"
        + "ospf:extended-prefix-opaque/"
        + "ospf:extended-prefix-tlv" {
    when "derived-from-or-self(../../../../../../../../../.."
       + "/rt:type, 'ospf:ospfv2')" {
      description
        "This augmentation is only valid for OSPFv2.";
    }
    description
      "Flex-algo prefix metric sub-TLVs for OSPFv2 extended
       prefix TLV in type 11 opaque LSA.";
    uses fapm-sub-tlvs;
  }

  /* Flex-algo prefix metric Sub-TLV in OSPFv3 Inter-Area
     Prefix TLV */

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-inter-area-prefix/"
        + "ospfv3-e-lsa:e-inter-prefix-tlvs/"
        + "ospfv3-e-lsa:inter-prefix-tlv" {
    when "derived-from-or-self(../../../../../../../../../../../.."
       + "/rt:type, 'ospf:ospfv3')" {
      description
        "This augmentation is only valid for OSPFv3
         E-Router LSAs";
    }
    uses fapm-sub-tlvs;
    description
      "OSPFv3 Area-Scoped Inter-Area Prefix TLV.";
  }

  /* Flex-algo prefix metric Sub-TLV in OSPFv3 External Prefix TLV */

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body/ospfv3-e-lsa:e-as-external/"
        + "ospfv3-e-lsa:e-external-tlvs/"
        + "ospfv3-e-lsa:external-prefix-tlv" {
    when "derived-from-or-self(../../../../../../../../../.."
       + "/rt:type, 'ospf:ospfv3')" {
      description
        "This augmentation is only valid for OSPFv3.";
    }
    uses fapm-sub-tlvs;
    description
      "OSPFv3 AS-Scoped External Prefix TLV.";
  }

  /* OSPFv2 Extended Inter-Area ASBR LSA */

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque" {
    when "derived-from-or-self(../../../../../../../../../.."
       + "/rt:type, 'ospf:ospfv2')" {
      description
        "This augmentation is only valid for OSPFv2.";
    }
    description
      "OSPFv2 Extended Inter-Area ASBR LSA in type 10
       opaque LSA.";
    container eia-asbr-opaque {
      container eia-asbr-tlv {
        leaf asbr-rtr-id {
          type rt-types:router-id;
          description
            "The OSPF Router ID of the ASBR.";
        }
        uses faam-sub-tlvs;
        uses ospf:unknown-tlvs;
        description
          "EIA-ASBR TLV, used to advertise additional attributes
           associated with the reachability of an ASBR.";
      }
      uses ospf:unknown-tlvs;
      description
        "OSPFv2 Extended Inter-Area (EIA-ASBR) opaque LSA.";
    }
  }

  /* FAAM Sub-TLV in OSPFv3 Inter-Area-Router TLV */

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-inter-area-router/"
        + "ospfv3-e-lsa:e-inter-router-tlvs/"
        + "ospfv3-e-lsa:inter-router-tlv" {
    when "derived-from-or-self(../../../../../../../../../../../.."
       + "/rt:type, 'ospf:ospfv3')" {
      description
        "This augmentation is only valid for OSPFv3
         Inter-Area-Router TLV.";
    }
    uses faam-sub-tlvs;
    description
      "OSPFv3 Area-Scoped Inter-Area-Router TLV.";
  }

  /* Notification */

  notification flex-algo-not-supported {
    leaf routing-protocol-name {
      type leafref {
        path "/rt:routing/rt:control-plane-protocols/"
           + "rt:control-plane-protocol/rt:name";
      }
      description
        "Name of the OSPF instance.";
    }
    leaf algo-number {
      type uint8;
      description
        "Flex-algo identifier which is not supported by the OSPF
         instance. A value not in the inclusive range of 128-255
         is indicative of an invalid FAD algorithm specification.";
    }
    description
      "This notification is sent when an OSPF instance does not
       support this flex-algo.";
  }
}
