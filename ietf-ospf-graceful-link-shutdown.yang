module ietf-ospf-graceful-link-shutdown {
  yang-version 1.1;
  namespace
    "urn:ietf:params:xml:ns:yang:ietf-ospf-graceful-link-shutdown";

  prefix ospf-grace-linkdown;

  import ietf-inet-types {
    prefix "inet";
    reference "RFC 6991: Common YANG Data Types";
  }

  import ietf-routing {
    prefix "rt";
    reference "RFC 8349: A YANG Data Model for Routing
               Management (NMDA Version)";
  }

  import ietf-ospf {
    prefix "ospf";
    reference "RFC 9129 - YANG Data Model for the OSPF
               Protocol";
  }

  import ietf-ospfv3-extended-lsa {
    prefix "ospfv3-e-lsa";
    reference "RFC 9587: YANG Data Model for OSPFv3 Extended Link
               State Advertisements (LSAs)";
  }

  organization
    "IETF LSR - Link State Routing Working Group";

  contact
     "WG Web:   <https://datatracker.ietf.org/wg/lsr/>
      WG List:  <mailto:lsr@ietf.org>

      Author:   Yingzhen Qu
                <mailto:yingzhen.ietf@gmail.com>
      Author:   Acee Lindem
                <mailto:acee.ietf@gmail.com>";

  description
    "This YANG module defines the configuration and operational
     state for OSPF Graceful Link Shutdown feature as defined
     in RFC 8379.

     This YANG model conforms to the Network Management
     Datastore Architecture (NDMA) as described in RFC 8342.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.";

  reference "RFC XXXX";

  revision 2024-07-01 {
    description
      "Initial version";
    reference
      "RFC XXXX: OSPF YANG Model Augmentations for Additional
                 Features - Version 1.";
  }


  /* RFC 8379 */
  augment "/rt:routing/rt:control-plane-protocols/"
        + "rt:control-plane-protocol/ospf:ospf/"
        + "ospf:areas/ospf:area/ospf:interfaces/ospf:interface" {
    when "../../../../../rt:type = 'ospf:ospfv2' or "
       + "../../../../../rt:type = 'ospf:ospfv3'" {
      description
        "This augments the OSPF interface configuration
         when used.";
    }
    description
      "This augments the OSPF protocol interface
       configuration with segment routing.";

    container graceful-link-shutdown {
      leaf enable {
        type boolean;
        default false;
        description
          "Enable OSPF graceful link shutdown.";
      }
      description
        "OSPF Graceful Link Shutdown.";
    }
  }


  /* Database */
  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-link-opaque/ospf:extended-link-tlv" {
    when "../../../../../../../../../../../../"
       + "rt:type = 'ospf:ospfv2'" {
      description
        "This augmentation is only valid for OSPFv2.";
    }
    description
      "OSPF graceful link shutdown for OSPFv2 extended link TLV
       in type 10 opaque LSA.";

    container graceful-link-shutdown-sub-tlv {
      presence "Enable graceful link shutdown";
      description
        "Graceful-Link-Shutdown sub-TLV identifies the link as being
         gracefully shutdown.";
    }

    container remote-address-sub-tlv {
      leaf remote-address {
         type inet:ipv4-address;
         description
           "Remote IPv4 address used to identify a particular link
            on the remote side.";
      }
      description
        "This sub-TLV specifies the IPv4 address of the remote
         endpoint on the link.";
    }

    container local-remote-int-id-sub-tlv {
      leaf local-int-id {
         type uint32;
         description "Local interface ID.";
      }
      leaf remote-int-id {
         type uint32;
         description "Remote interface ID.";
      }
      description
        "This sub-TLV specifies Local and Remote Interface IDs.";
    }
  }

  augment "/rt:routing/"
       + "rt:control-plane-protocols/rt:control-plane-protocol/"
       + "ospf:ospf/ospf:areas/ospf:area/ospf:database/"
       + "ospf:area-scope-lsa-type/ospf:area-scope-lsas/"
       + "ospf:area-scope-lsa/ospf:version/ospf:ospfv3/"
       + "ospf:ospfv3/ospf:body/ospfv3-e-lsa:e-router"
       + "/ospfv3-e-lsa:e-router-tlvs/ospfv3-e-lsa:link-tlv" {
       when "'ospf:../../../../../../../../../"
         + "rt:type' = 'ospf:ospfv3'" {
         description
           "This augmentation is only valid for OSPFv3
            E-Router LSAs";
       }
    container graceful-link-shutdown-sub-tlv {
      presence "Enable graceful link shutdown";
      description
        "Graceful-Link-Shutdown sub-TLV identifies the link as being
         gracefully shutdown.";
    }
    description
      "Augment OSPFv3 Area scope router-link TLV.";
  }
}
