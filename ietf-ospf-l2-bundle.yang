module ietf-ospf-l2-bundle {
  yang-version 1.1;
  namespace "urn:ietf:params:xml:ns:yang:ietf-ospf-l2-bundle";

  prefix ospf-l2-bundle;

  import ietf-routing-types {
    prefix rt-types;
    reference 
      "RFC 8294: Common YANG Data Types for the Routing Area";
  }

  import ietf-routing {
    prefix rt;
    reference 
      "RFC 8349: A YANG Data Model for Routing
                 Management (NMDA Version)";
  }

  import ietf-ospf {
    prefix ospf;
    reference 
      "RFC 9129: YANG Data Model for the OSPF Protocol";
  }

  import ietf-ospf-link-attr {
    prefix ospf-link-attr;
  }

  import ietf-ospfv3-extended-lsa {
    prefix ospfv3-e-lsa;
    reference
      "RFC 9587 - YANG Data Model for OSPFv3 Extended LSAs";
  }

  import ietf-ospf-sr-mpls {
    prefix ospf-sr-mpls;
  }

  organization
    "IETF LSR - Link State Routing Working Group";

  contact
     "WG Web:   <https://datatracker.ietf.org/wg/lsr/>
      WG List:  <mailto:lsr@ietf.org>

      Author:   Yingzhen Qu
                <mailto:yqu@futurewei.com>
      Author:   Acee Lindem
                <mailto:acee.ietf@gmail.com>";

  description
    "This YANG module defines the configuration and operational
     state for Advertising Layer 2 Bundle Member Link Attributes
     in OSPF as defined in RFC 9356.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.";

  reference "RFC XXXX";

  revision 2025-02-27 {
    description
      "Initial version";
    reference
      "RFC XXXX: OSPF YANG Model Augmentations for Additional
                 Features - Version 1";
  }

  /* Groupings */
  grouping ospfv2-member-link-attr-sub-tlvs {
    description
      "OSPFv2 L2 Bundle Member Attributes sub-TLV (RFC 9356).";

    container adj-sid-sub-tlvs {
      list adj-sid-sub-tlv {
        description
          "List of adj-sid sub-tlvs.";
        container adj-sid-flags {
          leaf-list flags {
            type identityref {
              base ospf-sr-mpls:adj-sid-flag;
            }
          description
            "Adj-SID sub-TLV flags.";
          }
          description
            "Adj-sid sub-TLV flags.";
        }
        leaf mt-id {
          type uint8;
          description
            "Multi-topology ID. Topologies range from 0-127 and
             return of any other value would indicate an error.";
          reference
            "RFC 4915 - Multi-Topology (MT) Routing in OSPF";
        }
        leaf weight {
          type uint8;
          description
            "Weight used for load-balancing.";
        }
        leaf sid {
          type uint32;
          description
            "Segment Identifier (SID) - A 20 bit label or
             an index into the SID/Label space.";
        }
      }
      description
        "Adjacency SID sub-tlvs.";
    }
    container lan-adj-sid-sub-tlv {
      description
        "LAN Adj-SID optional sub-TLVs.";
      list lan-adj-sid-sub-tlv {
        description
          "List of LAN Adj-SID sub-TLVs.";
        container lan-adj-sid-flags {
          leaf-list flags {
            type identityref {
              base ospf-sr-mpls:adj-sid-flag;
            }
            description
              "LAN Adj-SID sub-TLV flags.";
          }
          description
            "LAN Adj-SID sub-TLV flags.";
        }
        leaf mt-id {
          type uint8;
          description
            "Multi-topology ID. Topologies range from 0-127 and
             return of any other value would indicate an error.";
          reference
            "RFC 4915 - Multi-Topology (MT) Routing in OSPF";
        }
        leaf weight {
          type uint8;
          description
            "Weight used for load-balancing.";
        }
        leaf neighbor-router-id {
          type rt-types:router-id;
          description
            "Neighbor router ID.";
        }
        leaf sid {
          type uint32;
          description
            "Segment Identifier (SID) - A 20 bit label or
             an index into the SID/Label space.

             If the  V-Flag is set to 0 and L-Flag is set to 0:
             The SID/Index/Label field is a 4-octet index defining
             the offset in the SID/Label space advertised by this
             router.

             If V-Flag is set to 1 and L-Flag is set to 1: The
             SID/Index/Label field is a 3-octet local label where
             the 20 rightmost bits are used for encoding the label
             value.";
        }
      }
    }

    uses ospf-link-attr:app-specific-link-attr-sub-tlvs;
  }

  grouping ospfv3-member-link-attr-sub-tlvs {
    description
      "OSPFv3 L2 Bundle Member Attributes sub-TLV (RFC 9356).";

    uses ospf-sr-mpls:ospfv3-adj-sid-sub-tlvs;
    uses ospf-sr-mpls:ospfv3-lan-adj-sid-sub-tlvs;
    uses ospf-link-attr:app-specific-link-attr-sub-tlvs;
  }

  /* Configuration */
  augment "/rt:routing/rt:control-plane-protocols/"
        + "rt:control-plane-protocol/ospf:ospf/"
        + "ospf:areas/ospf:area/ospf:interfaces/ospf:interface" {
    when "derived-from(/rt:routing/rt:control-plane-protocols/"
       + "rt:control-plane-protocol/rt:type, 'ospf:ospf')" {
      description
        "This augments the OSPF routing protocol when used.";
    }
    description
      "This augments the OSPF interface configuration with L2
       Bundle Member Attributes.";

    container l2-mbr-attrs {
      description
        "L2 member attributes configuration.";
      list l2-mbr-attr {
        key l2-bdl-mbr-dscpr;
        leaf l2-bdl-mbr-dscpr {
          type uint32;
          description
            "L2 bundle member descriptor: a 4-octet link-local
             identifier for the member link.";
        }
        leaf adj-sid {
          type uint32;
          description
            "Value of the Adj-SID.";
        }
        leaf lan-adj-sid {
          type uint32;
          description
            "Value of the LAN-Adj-SID.";
        } 
        /* More configuration can be added here */              
        description
          "List of L2 bundle members.";
      }
    }

  }

  /* Database */
  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-link-opaque/ospf:extended-link-tlv" {
    when "derived-from(/rt:routing/rt:control-plane-protocols/"
         + "rt:control-plane-protocol/rt:type, 'ospf:ospfv2')" {
      description
        "This augmentation is only valid for OSPFv2.";
    }
    description
      "OSPFv2 L2 Bundle Member Attributes sub-TLV is
       a sub-TLV of OSPFv2 Extended Link TLV (RFC7684).";

    container l2-bdl-mbr-attr {
      list l2-bdl-mbrs {
        description
          "List of L2 bundle members.";
        leaf l2-bdl-mbr-dscpr {
          type uint32;
          description
            "L2 bundle member descriptor: a 4-octet link-local
             identifier for the member link.";
        }
        uses ospfv2-member-link-attr-sub-tlvs;
      }
      description
        "OSPFv2 L2 Bundle Member Attributes sub-TLV.";
    }
  }

  augment "/rt:routing/"
       + "rt:control-plane-protocols/rt:control-plane-protocol/"
       + "ospf:ospf/ospf:areas/ospf:area/ospf:database/"
       + "ospf:area-scope-lsa-type/ospf:area-scope-lsas/"
       + "ospf:area-scope-lsa/ospf:version/ospf:ospfv3/"
       + "ospf:ospfv3/ospf:body/ospfv3-e-lsa:e-router/"
       + "ospfv3-e-lsa:e-router-tlvs/ospfv3-e-lsa:link-tlv" {
    when "derived-from(/rt:routing/rt:control-plane-protocols/"
         + "rt:control-plane-protocol/rt:type, 'ospf:ospfv3')" {
         description
           "This augmentation is only valid for OSPFv3
            E-Router LSAs";
       }
    description
      "Augment OSPFv3 Area scope router-link TLV.";

    container l2-bdl-mbr-attr {
      list l2-bdl-mbrs {
        description
          "List of L2 bundle members.";
        leaf l2-bdl-mbr-dscpr {
          type uint32;
          description
            "L2 bundle member descriptor: a 4-octet link-local
             identifier for the member link.";
        }
        uses ospfv3-member-link-attr-sub-tlvs;
      }
      description
        "OSPFv3 L2 Bundle Member Attributes sub-TLV.";
    }
  }
}
