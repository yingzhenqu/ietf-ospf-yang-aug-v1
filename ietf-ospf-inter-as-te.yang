module ietf-ospf-inter-as-te {
  yang-version 1.1;
  namespace "urn:ietf:params:xml:ns:yang:ietf-ospf-inter-as-te";

  prefix ospf-inter-as-te;

  import ietf-inet-types {
    prefix inet;
    reference 
      "RFC 6991: Common YANG Data Types";
  }

  import ietf-routing-types {
    prefix rt-types;
    reference 
      "RFC 8294: Common YANG Data Types for the Routing Area";
  }

  import ietf-routing {
    prefix rt;
    reference 
      "RFC 8349: A YANG Data Model for Routing
                 Management (NMDA Version)";
  }

  import ietf-ospf {
    prefix ospf;
    reference 
      "RFC 9129: YANG Data Model for the OSPF Protocol";
  }

  import ietf-ospf-te {
    prefix ospf-te;
    reference
      "RFC 3630: Traffic Engineering (TE) Extensions to OSPF Version 2
       RFC 5329: Traffic Engineering Extensions to OSPF Version 3";
  }

  organization
    "IETF LSR - Link State Routing Working Group";

  contact
     "WG Web:   <https://datatracker.ietf.org/wg/lsr/>
      WG List:  <mailto:lsr@ietf.org>

      Author:   Yingzhen Qu
                <mailto:yqu@futurewei.com>
      Author:   Acee Lindem
                <mailto:acee.ietf@gmail.com>";

  description
    "This YANG module defines the configuration and operational
     state for OSPF Extensions in Support of Inter-Autonomous
     System (AS) MPLS and GMPLS Traffic Engineering as defined
     in RFC 5392.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.";

  reference "RFC XXXX";

  revision 2025-02-27 {
    description
      "Initial version";
    reference
      "RFC XXXX: OSPF YANG Model Augmentations for Additional
                 Features - Version 1";
  }

  identity ospfv3-intra-area-te-lsa {
    base ospf:ospfv3-lsa-type;
    description
      "OSPFv3 Intrea-area TE LSA.";
  }

  grouping inter-as-te-v2-lsa {
    description
      "Grouping for OSPF Inter-AS-TE-2 LSA.";
    container inter-as-te-v2 {
      description
        "The Inter-AS-TE-v2 LSA.";

      container link-tlv {
        description
          "Describes a single link.  It is constructed
           from a set of sub-TLVs.";
        leaf link-type {
          type ospf:router-link-type;
          mandatory true;
          description
            "Link type.";
        }
        container local-if-ipv4-addrs {
          description
            "All local interface IPv4 addresses.";
          leaf-list local-if-ipv4-addr {
            type inet:ipv4-address;
            description
              "List of local interface IPv4 addresses.";
          }
        }
        container remote-if-ipv4-addrs {
          description
            "All remote interface IPv4 addresses.";
          leaf-list remote-if-ipv4-addr {
            type inet:ipv4-address;
            description
              "List of remote interface IPv4 addresses.";
          }
        }
        leaf te-metric {
          type uint32;
          description
            "TE metric.";
        }
        leaf max-bandwidth {
          type rt-types:bandwidth-ieee-float32;
          description
            "Maximum bandwidth.";
        }
        leaf max-reservable-bandwidth {
          type rt-types:bandwidth-ieee-float32;
          description
            "Maximum reservable bandwidth.";
        }
        container unreserved-bandwidths {
          description
            "All unreserved bandwidths.";
          list unreserved-bandwidth {
            leaf priority {
              type uint8 {
                range "0 .. 7";
              }
            description
              "Priority from 0 to 7.";
               }
            leaf unreserved-bandwidth {
              type rt-types:bandwidth-ieee-float32;
              description
                "Unreserved bandwidth.";
            }
            description
              "List of unreserved bandwidths for different
               priorities.";
          }
        }
        leaf admin-group {
          type uint32;
          description
            "Administrative Group / Resource Class/Color.";
        }
        leaf remote-as-number {
          type uint32;
          mandatory true;
          description
            "Remote AS number.";
        }
        leaf ipv4-remote-asbr-id {
          type inet:ipv4-address;
          description
            "The neighboring ASBR IPv4 address.";
        }
        leaf ipv6-remote-asbr-id {
          type inet:ipv6-address;
          description
            "The neighboring ASBR IPv6 address.";
        }
        uses ospf:unknown-tlvs;
      }
    }
  }
  grouping inter-as-te-v3 {
    description
      "Grouping for OSPFv3 inter-as-te-v3 lsa.";
    container inter-as-te-v3 {
      container link-tlv {
        description 
          "Describes a single link, and it is constructed
           of a set of Sub-TLVs.";
        leaf link-type {
          type ospf:router-link-type;
          mandatory true;
          description
            "Link type.";
        }

        container local-if-ipv6-addrs {
          description
            "All local interface IPv6 addresses.";
          leaf-list local-if-ipv6-addr {
            type inet:ipv6-address;
            description
              "List of local interface IPv6 addresses.";
          }
        }

        container remote-if-ipv6-addrs {
          description
            "All remote interface IPv6 addresses.";
          leaf-list remote-if-ipv6-addr {
            type inet:ipv6-address;
            description
              "List of remote interface IPv6 addresses.";
          }
        }

        leaf te-metric {
          type uint32;
          description
            "TE metric.";
        }

        leaf max-bandwidth {
          type rt-types:bandwidth-ieee-float32;
          description
            "Maximum bandwidth.";
        }

        leaf max-reservable-bandwidth {
          type rt-types:bandwidth-ieee-float32;
          description
            "Maximum reservable bandwidth.";
        }

        container unreserved-bandwidths {
          description
            "All unreserved bandwidths.";
          list unreserved-bandwidth {
            leaf priority {
              type uint8 {
                range "0 .. 7";
              }
              description
                "Priority from 0 to 7.";
            }
            leaf unreserved-bandwidth {
              type rt-types:bandwidth-ieee-float32;
              description
                "Unreserved bandwidth.";
            }
            description
              "List of unreserved bandwidths for different
               priorities.";
          }
        }

        leaf admin-group {
          type uint32;
          description
            "Administrative group/Resource Class/Color.";
        }

        leaf remote-as-number {
          type uint32;
          mandatory true;
          description
            "Remote AS number.";
        }
        leaf ipv4-remote-asbr-id {
          type inet:ipv4-address;
          description
            "The neighboring ASBR IPv4 address.";
        }
        leaf ipv6-remote-asbr-id {
          type inet:ipv6-address;
          description
            "The neighboring ASBR IPv6 address.";
        }
        uses ospf:unknown-tlvs;
      }

      description
        "OSPFv3 Inter-AS-TE-v3 LSA.";
      reference
        "RFC 5392: TOSPF Extensions in Support of Inter-Autonomous
         System (AS) MPLS and GMPLS Traffic Engineering";
    }
  }

  /* Configuration */
  augment "/rt:routing/"
        + "rt:control-plane-protocols/rt:control-plane-protocol/"
        + "ospf:ospf/ospf:mpls/ospf-te:traffic-eng" {
    when "derived-from(/rt:routing/rt:control-plane-protocols/"
          + "rt:control-plane-protocol/rt:type, 'ospf:ospf')" {
      description
        "This augment OSPF routing protocol when used";
    }
    description
      "This augments OSPF protocol traffic engineering configuration
       with Inter-AS-TE configuration.";
    container inter-as-te {
      presence "Enable Inter-AS-TE";
      description
        "OSPFv3 MPLS TE configuration.";
      leaf flood-as-wide {
        type boolean;
        default "false";
        description
          "Enables as-scoped traffic engineering advertisement. By
           default, the inter-as TE link advertisement is limited to
           within the single area.";
      }
      reference
        "RFC 5392: OSPF Extensions in Support of Inter-Autonomous
                   System (AS) MPLS and GMPLS Traffic Engineering";
    }
  }

  /* Database */
  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque" {
    when "derived-from(/rt:routing/rt:control-plane-protocols/"
         + "rt:control-plane-protocol/rt:type, 'ospf:ospfv2')" {
      description
        "This augments OSPFv2 routing protocol when used";         
         }
      description
        "OSPFv2 type 10 Opaque LSA.";
      uses inter-as-te-v2-lsa;
    }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque" {
    when "derived-from(/rt:routing/rt:control-plane-protocols/"
         + "rt:control-plane-protocol/rt:type, 'ospf:ospfv2')" {
      description
        "This augments OSPFv2 routing protocol when used";         
         }
      description
        "OSPFv2 type 11 Opaque LSA.";
      uses inter-as-te-v2-lsa;
    } 

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv3/"
        + "ospf:ospfv3/ospf:body" {
    when "derived-from(/rt:routing/rt:control-plane-protocols/"
         + "rt:control-plane-protocol/rt:type, 'ospf:ospfv3')" {
      description
        "This augmentation is only valid for OSPFv3.";
    }
    description
      "OSPFv3 Intra-Area-TE-LSA.";

    uses inter-as-te-v3;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body" {
    when "derived-from(/rt:routing/rt:control-plane-protocols/"
         + "rt:control-plane-protocol/rt:type, 'ospf:ospfv3')" {
      description
        "This augmentation is only valid for OSPFv3.";
    }
    description
      "OSPFv3 Intra-Area-TE-LSA.";

    uses inter-as-te-v3;
  }
}
